[DOCUMENT]
TITLE: Using strictDoc PoC
OPTIONS:
  AUTO_LEVELS: Off

[GRAMMAR]
ELEMENTS:
- TAG: REQUIREMENT
  FIELDS:
  - TITLE: UID
    TYPE: String
    REQUIRED: False
  - TITLE: LEVEL
    TYPE: String
    REQUIRED: True
  - TITLE: STATUS
    TYPE: String
    REQUIRED: False
  - TITLE: TITLE
    TYPE: String
    REQUIRED: True
  - TITLE: STATEMENT
    TYPE: String
    REQUIRED: False
  RELATIONS:
  - TYPE: Parent
    ROLE: Derives
  - TYPE: Parent
    ROLE: Depends
  - TYPE: Parent
    ROLE: Satisfies
  - TYPE: Parent
    ROLE: Validates
  - TYPE: File

[SECTION]
LEVEL: 1
TITLE: Business requirements

[REQUIREMENT]
UID: BUS-PROVIDE-QUALITY-EDUCATION-SOFTWARE-DESIGN
LEVEL: BUSINESS
STATUS: Active
TITLE: Provide quality education on software design
STATEMENT: >>>
To provide the students with quality education on the principles of software design.
<<<

[/SECTION]

[SECTION]
LEVEL: 2
TITLE: Stakeholder requirements

[REQUIREMENT]
UID: STAKE-PROVIDE-QUALITY-EDUCATION-SOFTWARE-ANALYSIS
LEVEL: STAKEHOLDER
STATUS: Active
TITLE: Provide quality education on software analysis
STATEMENT: >>>
Teacher / To provide the students with quality education on software analysis.
<<<
RELATIONS:
- TYPE: Parent
  VALUE: BUS-PROVIDE-QUALITY-EDUCATION-SOFTWARE-DESIGN
  ROLE: Derives

[REQUIREMENT]
UID: STAKE-PROVIDE-QUALITY-EDUCATION-TRACEABILITY
LEVEL: STAKEHOLDER
STATUS: Active
TITLE: Provide quality education on requirements traceability
STATEMENT: >>>
Teacher / To provide the students with common real-world examples of requirements traceability in a visual way.
<<<
RELATIONS:
- TYPE: Parent
  VALUE: STAKE-PROVIDE-QUALITY-EDUCATION-SOFTWARE-ANALYSIS
  ROLE: Derives

[REQUIREMENT]
UID: STAKE-EMPLOY-EASY-VISUAL-TOOL
LEVEL: STAKEHOLDER
STATUS: Active
TITLE: Employ an easy-to-use visual tool
STATEMENT: >>>
Teacher / To employ an easy-to-use SW tool that shows basic principles of requirements traceability for common real-world examples in a visual way.
<<<
RELATIONS:
- TYPE: Parent
  VALUE: STAKE-PROVIDE-QUALITY-EDUCATION-TRACEABILITY
  ROLE: Derives

[/SECTION]

[SECTION]
LEVEL: 3
TITLE: Solution requirements

[REQUIREMENT]
UID: SOL-SUPPORT-MODELS-METHODOLOGIES
LEVEL: SOLUTION
STATUS: Active
TITLE: Support common models and methodologies of SW development
STATEMENT: >>>
The system shall support common models and methodologies of SW development.
<<<
RELATIONS:
- TYPE: Parent
  VALUE: STAKE-EMPLOY-EASY-VISUAL-TOOL
  ROLE: Derives

[REQUIREMENT]
UID: SOL-SUPPORT-WATERFALL-IIM-AGILE
LEVEL: SOLUTION
STATUS: Active
TITLE: Support waterfall, iterative-incremental and agile methodologies
STATEMENT: >>>
The system shall support waterfall model, iterative-incremental model of SW development and agile methodologies.
<<<
RELATIONS:
- TYPE: Parent
  VALUE: SOL-SUPPORT-MODELS-METHODOLOGIES
  ROLE: Derives

[REQUIREMENT]
UID: SOL-CUSTOM-ITEM-TYPES
LEVEL: SOLUTION
STATUS: Active
TITLE: Custom item types
STATEMENT: >>>
The system shall allow the user to define their own item types.
<<<
RELATIONS:
- TYPE: Parent
  VALUE: SOL-SUPPORT-WATERFALL-IIM-AGILE
  ROLE: Derives

[REQUIREMENT]
UID: SOL-CUSTOM-USER-LEVEL
LEVEL: SOLUTION
STATUS: Active
TITLE: Custom user levels
STATEMENT: >>>
The system shall allow the user to define their own user levels.
<<<
RELATIONS:
- TYPE: Parent
  VALUE: SOL-SUPPORT-WATERFALL-IIM-AGILE
  ROLE: Derives

[REQUIREMENT]
UID: SOL-REQUIRED-FIELDS-FOR-LEVEL-DEFINITION
LEVEL: SOLUTION
STATUS: Active
TITLE: Required fields for level definition
STATEMENT: >>>
The system shall require the user to define color, name and order for each user level.
<<<
RELATIONS:
- TYPE: Parent
  VALUE: SOL-CUSTOM-USER-LEVEL
  ROLE: Derives

[REQUIREMENT]
UID: SOL-VIS-MANAGEMENT-TRACEABILITY-HIERARCHY
LEVEL: SOLUTION
STATUS: Active
TITLE: Visual management of traceability hierarchy
STATEMENT: >>>
The system shall enable visual management of traceability hierarchy.
<<<
RELATIONS:
- TYPE: Parent
  VALUE: STAKE-EMPLOY-EASY-VISUAL-TOOL
  ROLE: Derives

[REQUIREMENT]
UID: SOL-EDITING-ITEMS
LEVEL: SOLUTION
STATUS: Active
TITLE: Editing items and relationships
STATEMENT: >>>
The system shall support adding editing/removing attributes and properties of hierarchy items and relationships.
<<<
RELATIONS:
- TYPE: Parent
  VALUE: SOL-VIS-MANAGEMENT-TRACEABILITY-HIERARCHY
  ROLE: Derives

[REQUIREMENT]
UID: SOL-VISUAL-EDITING-ITEMS
LEVEL: SOLUTION
STATUS: Active
TITLE: Visual editing items and relationships
STATEMENT: >>>
The system shall support visual adding / editing / removing hierarchy items and their relationships.
<<<
RELATIONS:
- TYPE: Parent
  VALUE: SOL-VIS-MANAGEMENT-TRACEABILITY-HIERARCHY
  ROLE: Derives

[REQUIREMENT]
UID: SOL-SPLITTING-TO-INTERNAL-LEVELS
LEVEL: SOLUTION
STATUS: Active
TITLE: Splitting to internal levels
STATEMENT: >>>
The system shall support adding hierarchy items and their relationships in such a way that a user level may consist of one or more internal levels.
<<<
RELATIONS:
- TYPE: Parent
  VALUE: SOL-VISUAL-EDITING-ITEMS
  ROLE: Derives

[REQUIREMENT]
UID: SOL-ITEM-TYPE-UNIQUENESS
LEVEL: SOLUTION
TITLE: Type uniqueness
STATEMENT: >>>
The system shall require the user to choose exactly one item type for each hierarchy item added (either predefined item type or user defined item type).
<<<
RELATIONS:
- TYPE: Parent
  VALUE: SOL-VISUAL-EDITING-ITEMS
  ROLE: Derives

[REQUIREMENT]
UID: SOL-ITEM-LEVEL-UNIQUENESS
LEVEL: SOLUTION
TITLE: Level uniqueness
STATEMENT: >>>
The system shall require the user to choose exactly one user level for each requirement added.
<<<
RELATIONS:
- TYPE: Parent
  VALUE: SOL-VISUAL-EDITING-ITEMS
  ROLE: Derives

[REQUIREMENT]
UID: SOL-VISUAL-DISPLAY-TRACEABILITY-HIERARCHY
LEVEL: SOLUTION
STATUS: Active
TITLE: Visual display of traceability hierarchy
STATEMENT: >>>
The system shall display visually the traceability hierarchy.
<<<
RELATIONS:
- TYPE: Parent
  VALUE: STAKE-EMPLOY-EASY-VISUAL-TOOL
  ROLE: Derives

[REQUIREMENT]
UID: SOL-VISUAL-LINEAGE
LEVEL: SOLUTION
STATUS: Active
TITLE: Visual lineage
STATEMENT: >>>
The system shall display visually backward / forward / overall linage of a single hierarchy item.
<<<
RELATIONS:
- TYPE: Parent
  VALUE: STAKE-EMPLOY-EASY-VISUAL-TOOL
  ROLE: Derives

[REQUIREMENT]
UID: SOL-VISUAL-HIERARCHY-VERSIONING
LEVEL: SOLUTION
STATUS: Active
TITLE: Visual hierarchy versioning
STATEMENT: >>>
The system shall display different versions of traceability hierarchy.
<<<
RELATIONS:
- TYPE: Parent
  VALUE: STAKE-EMPLOY-EASY-VISUAL-TOOL
  ROLE: Derives

[REQUIREMENT]
UID: SOL-INFORM-TRACEABILITY-ISSUES
LEVEL: SOLUTION
STATUS: Active
TITLE: Inform about traceability issues
STATEMENT: >>>
The system shall inform the user about traceability issues within the traceability hierarchy.
<<<
RELATIONS:
- TYPE: Parent
  VALUE: STAKE-EMPLOY-EASY-VISUAL-TOOL
  ROLE: Derives

[REQUIREMENT]
UID: SOL-ERROR-PARENT-REQUIREMENT-ABSENCE
LEVEL: SOLUTION
TITLE: Parent requirement absence informing
STATEMENT: >>>
The system shall communicate traceability error if a requirement does not have a parent requirement and its user level is not the top user level.
<<<
RELATIONS:
- TYPE: Parent
  VALUE: SOL-INFORM-TRACEABILITY-ISSUES
  ROLE: Derives

[REQUIREMENT]
UID: SOL-DISPLAY-USER-LEVEL-COLOR
LEVEL: SOLUTION
STATUS: Active
TITLE: Display user level color
STATEMENT: >>>
The system shall display a requirement in the color of its user level.
<<<
RELATIONS:
- TYPE: Parent
  VALUE: SOL-VISUAL-DISPLAY-TRACEABILITY-HIERARCHY
  ROLE: Derives

[REQUIREMENT]
UID: SOL-VISUAL-DISPLAY-LEVELS-HIERARCHY
LEVEL: SOLUTION
STATUS: Active
TITLE: Visual display of levels hierarchy
STATEMENT: >>>
The system shall display user levels hierarchically based on their order.
<<<
RELATIONS:
- TYPE: Parent
  VALUE: SOL-VISUAL-DISPLAY-TRACEABILITY-HIERARCHY
  ROLE: Derives

[REQUIREMENT]
UID: SOL-DISPLAY-INTERNAL-LEVELS
LEVEL: SOLUTION
TITLE: todo: ask what that mean
STATEMENT: >>>
The system shall display internal levels of a user level hierarchically based on the relationships between the requirements in given user level.
<<<
RELATIONS:
- TYPE: Parent
  VALUE: SOL-VISUAL-DISPLAY-LEVELS-HIERARCHY
  ROLE: Derives

[REQUIREMENT]
UID: SOL-VISUAL-DISPLAY-IMPLEMENTATION-HIERARCHY
LEVEL: SOLUTION
STATUS: Active
TITLE: Visual display of implementation hierarchy
STATEMENT: >>>
The system shall enable to display implementation hierarchy items and their relationship to requirements automatically.
<<<
RELATIONS:
- TYPE: Parent
  VALUE: SOL-VISUAL-DISPLAY-TRACEABILITY-HIERARCHY
  ROLE: Derives

[/SECTION]
